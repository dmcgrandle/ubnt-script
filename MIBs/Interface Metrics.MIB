INTERFACE_METRICS_MIB DEFINITIONS ::= BEGIN

IMPORTS
OBJECT-TYPE, mib-2,
Integer32	FROM SNMPv2-SMI;

host     OBJECT IDENTIFIER ::= { mib-2 1000000 } 


routeChangeTable OBJECT-TYPE
    SYNTAX     SEQUENCE OF RouteChangeTableEntry
    MAX-ACCESS not-accessible
    STATUS     current
    DESCRIPTION
        "xxx"
    ::= { host 1 }

routeChangeTableEntry OBJECT-TYPE
    SYNTAX     RouteChangeTableEntry
    MAX-ACCESS not-accessible
    STATUS     current
    DESCRIPTION
        "xxx"
		
    INDEX { 
	DCN
	}
    ::= { routeChangeTable 1 }

RouteChangeTableEntry ::= SEQUENCE {	
		Destination			OCTET STRING,
		Flap	Integer32,
		Protocol	Integer32
    }
	
DCN OBJECT-TYPE
    SYNTAX     OCTET STRING
    MAX-ACCESS read-only
    STATUS     current
    DESCRIPTION
        "xxx"
    ::= { routeChangeTableEntry 1 }

Flap OBJECT-TYPE
    SYNTAX     Integer32 (0..100)
    MAX-ACCESS read-only
    STATUS     current
    DESCRIPTION
        "xxx"
    ::= { routeChangeTableEntry 2 }
	
Protocol OBJECT-TYPE
    SYNTAX     INTEGER {
                other     (1),  -- not specified
                local     (2),  -- local interface
                netmgmt   (3),  -- static route
                icmp      (4),  -- result of ICMP Redirect
                egp        (5),  -- Exterior Gateway Protocol
                ggp        (6),  -- Gateway-Gateway Protocol
                hello      (7),  -- FuzzBall HelloSpeak
                rip        (8),  -- Berkeley RIP or RIP-II
                isIs       (9),  -- Dual IS-IS
                esIs       (10), -- ISO 9542
                ciscoIgrp  (11), -- Cisco IGRP
                bbnSpfIgp  (12), -- BBN SPF IGP
                ospf       (13), -- Open Shortest Path First
                bgp        (14), -- Border Gateway Protocol
                idpr       (15), -- InterDomain Policy Routing
                ciscoEigrp (16)  -- Cisco EIGRP
             }
    MAX-ACCESS read-only
    STATUS     deprecated
    DESCRIPTION
           "xxx"
    ::= { routeChangeTableEntry 3 }



END
